FME workspace 04d_4_apply_static_unmasker_create_gbd_masks.fmw

Parameters:
- SourceDataset_GEOTIFF_2 = E:\Data\Harry\Documents\dial-a-map\fix_gbd_limits_with_old_africa_mask\out_only_fix_in_ZAF\Pf_PostHoc_ZeroAPIForcing_Limits_2*_5k.tif   # Source GeoTIFF File(s)
- DestDataset_GEOTIFF_4 = ..\Intermediary_Outputs\out_static_unmasked_for_gbd   # Destination GeoTIFF Folder

Readers:
- GEOTIFF_1: GEOTIFF from $(SourceDataset_GEOTIFF_2) in LL-WGS84

Writers:
- GEOTIFF_2: GEOTIFF to $(DestDataset_GEOTIFF_4)

Note: Read the previous iteration of the masks based on environmental limits and post-hoc masking polygons. Note that these have the south-africa-from-old-masks bodge applied manually
GEOTIFF (reader GEOTIFF_1)
    -> AttributeRenamer
AttributeRenamer
    ATTR_TABLE = RENAME_SET_DEFAULT fme_basename > _outname
    -> RasterBandInterpretationCoercer
    -> FeatureReader [INITIATOR]
FeatureReader
    GEOTIFF_READ_OFFSETS_IN_CS_UNITS = No
    GEOTIFF_FEATURE_TYPE_NAME = FORMAT_NAME
    GEOTIFF_IGNORE_RASTER_TYPE_KEY = No
    GEOTIFF_APPLY_GCPS = No
    OUTPUT_FEATURES_DISPLAY = Schema and Data Features
    INTERACT = <No Spatial Filter>
    ATTR_CONFLICT_RES = Use Result
    FORMAT = GEOTIFF
    DATASET = ..\Intermediary_Outputs\out_static_unmasker\static_unmasking_stamp.tif
    GEOTIFF_USE_SEARCH_ENVELOPE = NO
    ATTR_ACCUM_MODE = Merge Initiator and Result
    GEOTIFF_READER_META_ATTRIBUTES = fme_dataset fme_basename
    GEOTIFF_PREFER_FILE_CS_UNITS = Yes
    COMBINE_GEOM = Use Result
    <OTHER> -> FeatureHolder
Note: Ensure the "correction" masks arrive last to mosaicker by holding onto them. The mosaicker is set up to apply the last pixel arriving where there is an overlap.
FeatureHolder
    -> RasterBandInterpretationCoercer_2
Note: Recode nodata and value type to match
RasterBandInterpretationCoercer_2
    NUMERIC_TO_NUMERIC = Bounded cast
    FLOAT_TO_INTEGER = Round
    COLOR_TO_NUMERIC = Bounded cast
    INTERPRETATION = Int32
    -> RasterBandNodataSetter
RasterBandNodataSetter
    REPLACE_CELL_VALUES = Yes
    NODATA_VALUE = -9999
    -> RasterMosaicker
RasterBandInterpretationCoercer
    NUMERIC_TO_NUMERIC = Bounded cast
    FLOAT_TO_INTEGER = Round
    COLOR_TO_NUMERIC = Bounded cast
    INTERPRETATION = Int32
    -> RasterMosaicker
RasterMosaicker
    MERGE_PALETTES_NAME = Yes
    GROUP_BY = _outname
    ACCUM_ATTRS_NAME = Use Attributes From One Feature
    INTERPOLATION_TYPE_NAME = Nearest Neighbor
    SNAPPING_TYPE_NAME = Resample
    OVERLAPPING_VALUES = last
    NODATA_OVERWRITE = No
    -> GEOTIFF (writer GEOTIFF_2)
GEOTIFF (writer GEOTIFF_2)
