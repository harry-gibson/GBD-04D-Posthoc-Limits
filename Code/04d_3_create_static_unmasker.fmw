FME workspace 04d_3_create_static_unmasker.fmw

Parameters:
- DestDataset_GEOTIFF = ..\Intermediary_Outputs\out_static_unmasker   # Destination GeoTIFF Folder
- SourceDataset_ESRISHAPE = \\map-fs1.ndph.ox.ac.uk\map_data\GBD2017\Processing\Spatial_Data\MAP_Admin_Units\GBD2017_MAP_MG_5K_All-Units_Master-Geometries\MG_5K_GBD2017_ADMIN0.shp   # Source Esri Shapefile(s)
- SourceDataset_ESRISHAPE_3 = \\map-fs1.ndph.ox.ac.uk\map_data\GBD2017\Processing\Spatial_Data\MAP_Admin_Units\GBD2017_MAP_MG_5K_All-Units_Master-Geometries\MG_5K_GBD2017_ADMIN1.shp   # Source Esri Shapefile(s)

Readers:
- ESRISHAPE_1: ESRISHAPE from $(SourceDataset_ESRISHAPE)
- ESRISHAPE_2: ESRISHAPE from $(SourceDataset_ESRISHAPE_3)

Writers:
- GEOTIFF_1: GEOTIFF to $(DestDataset_GEOTIFF)

Note: Generating corrections to the "automatic" masks, i.e. the ones from the DB table. / If the DB table is wrong for whatever reason then we might want to unmask (i.e. set to 1 in the masks) certain areas. / This workbench is the first part of that: create a stamp that can be applied to the masks across all years to unmask certain areas.

Bookmark: Select the polygon(s) we want to unmask from the 5k jagged-edge shapefile(s)
MG_5K_GBD2017_ADMIN0 (reader ESRISHAPE_1)
    attributes: area_id long, fdef_id long, area_fstp char(100), area_fggt char(10), area_dset char(100), area_name char(120), iso3 char(3)
    -> Tester
Tester
    TEST_MODE = Automatic
    BOOL_OP = OR
    TEST_CLAUSE = TEST @Value(iso3) = PER
    TEST_DESCRIPTION = ""
    PASSED -> 3DForcer
MG_5K_GBD2017_ADMIN1 (reader ESRISHAPE_2)
    attributes: area_id long, fdef_id long, area_fstp char(100), area_fggt char(10), area_dset char(100), area_name char(120), iso3 char(3)
    -> Tester_2
Tester_2
    TEST_MODE = Automatic
    BOOL_OP = AND
    TEST_CLAUSE:
      TEST @Value(iso3) = BRA
      TEST @Value(area_name) = Acre
    TEST_DESCRIPTION = ""
    PASSED -> 3DForcer

Bookmark: Create a single static unmasking raster from them
3DForcer
    ZVALATTR = 1
    KEEPZVAL = No
    -> NumericRasterizer
NumericRasterizer
    BACKGROUND_VALUE = -9999
    FILL_WITH_NODATA = Yes
    GROUND_EXTENTS_MIN_X = -180
    GROUND_EXTENTS_MIN_Y = -60
    ANTI_ALIASING = No
    COLUMNS = 8640
    ROWCOL_OR_CELLSIZE = RowsColumns
    ROWS = 3480
    GROUND_EXTENTS_MAX_Y = 85
    TOLERANCE = 0.5
    INTERPRETATION_TYPE = Int32
    GROUND_EXTENTS_MAX_X = 180
    SPECIFY_GROUND_EXTENTS = Specify ground extents
    RASTER -> static_unmasking_stamp (writer GEOTIFF_1)
static_unmasking_stamp (writer GEOTIFF_1)
