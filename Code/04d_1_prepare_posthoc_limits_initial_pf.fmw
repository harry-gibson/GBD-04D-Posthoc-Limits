FME workspace 04d_1_prepare_posthoc_limits_initial_pf.fmw
Title: Generate GBS Posthoc Limits
Description: This workbench generates the annual limits rasters used in GBD modelling to mask out zero-malaria areas.
The actual regions to be masked (set to zero) are defined using database logic, using scripts maintained by Joe and documented separately in the RDS git repository. This workbench implements the results of that logic into annual rasters.
The output masks are based on a single "static" limits file that defines the limits of malaria based on environmental factors (and, since 09/18, the endemic/nonendemic status of the country). For each year, the zero-API polygons are read from the DB, rasterized, and set to zero in the mask.
Before output, any further "bodge" fixes required by the current iteration of headscratching are applied. These come and go and generally include things like copying a bit of a different raster or overwriting an area with "1".
The workbench has startup and shutdown python scripts which implement GBD stage workflows by archiving previous outputs and writing metadata.
Startup Python:
      # GBD - Archive outputs from any previous run
      # A version of this script should be run as a startup script in any GBD stages that are run using FME
      import fme
      import os, glob, datetime

      # build the paths based on the template stage folder layout relative to where the workbench itself is
      # Use abspath because fme occasionally does some weird escaping syntax on FME_MF_DIR
      codepath = os.path.abspath(fme.macroValues['FME_MF_DIR'])
      rootpath = os.path.dirname(codepath)
      # For this stage we have two types of run that should be considered separately so maintain subfolders below Checkpoint_Outputs
      checkpoint_path = os.path.join(rootpath, 'Checkpoint_Outputs', 'Pf')
      archive_path = os.path.join(checkpoint_path, 'Archive')

      prev_run_metadata_file = os.path.join(checkpoint_path, 'run_metadata.txt')
      if os.path.exists(prev_run_metadata_file):
          with open(prev_run_metadata_file, 'r') as f:
              prevRunTag = f.readline().strip("\n\r") + "-" + f.readline().strip("\n\r")
          # move them to a new subfolder under the archive named by runtime
          outdir = os.path.join(archive_path, prevRunTag)
          outdir_intermediate = os.path.join(outdir, "intermediates")
          outdir_out = os.path.join(outdir, "output")
          os.makedirs(outdir_intermediate)
          os.makedirs(outdir_out)
          # move everything except the readme file and the archive folder itself
          checkpoint_wildcard = os.path.join(checkpoint_path, '*')
          to_move = [f for f in glob.glob(checkpoint_wildcard)
              if not (os.path.basename(f).lower().startswith('readme'))
              and not (os.path.basename(f).lower() == 'archive')]
          for f in to_move:
              os.rename(f, os.path.join(outdir_out, os.path.basename(f)))

      else:
          # check if there are any outputs there- the folder might be clean so no problem
          if len(glob.glob(os.path.join(checkpoint_path,"*.tif"))) > 0:
              # cause an error
              logger = open(FME_LogFileName,'a')
              logger.write("Previous output data found but cannot find previous run metadata file. Please archive manually to continue!")
              raise Exception("Previous output data found but cannot find previous run metadata file. Please archive manually to continue!")
Shutdown Python:
      # FME python shutdown script to write out the metadata of this run, so that subsequent runs
      # will be able to read that metadata and use it to archive the outputs
      import fme
      import os, datetime
      # build the paths based on the template stage folder layout relative to where the workbench itself is
      codepath = os.path.abspath(fme.macroValues['FME_MF_DIR'])
      rootpath = os.path.dirname(codepath)
      checkpoint_path = os.path.join(rootpath, 'Checkpoint_Outputs', 'Pf')

      githash_file = os.path.join(codepath, 'githash.txt')
      if os.path.exists(githash_file):
          with open(githash_file, 'r') as f:
              githash = str(f.readline()) # str in case it's an all-numeric hash
      else:
          # cause an error
          assert False
      outTag = datetime.datetime.now().strftime('%Y_%m_%d_%H_%M_%S') + '\n' + githash
      outMDFile = os.path.join(checkpoint_path, 'run_metadata.txt')
      with open(outMDFile, 'w') as f:
          f.write(outTag)

Parameters:
- Environmental_Limits = \\map-fs1.ndph.ox.ac.uk\map_data\GBD2017\Processing\Spatial_Data\Static_Limits\Pf_Limits_EnvironmentalOnly_Endemic2017Only_5k.tif   # The existing environmental limits raster
- OutputFolder = ..\Checkpoint_Outputs\Pf   # Output folder - should be relative path to Checkpoint_Outputs
- IntermediateFolder = ..\Intermediary_Outputs   # Intermediate Output folder - should be relative path to Intermediary_Outputs
- SQL_Filename = zero_forcing_polygon_query.sql   # SQL file in workbench folder containing the query
- OldLimitsFileForBodge = ..\Code\static_data\Pf_limits_2014_stable_only.tif   # Africa2015 mask file for southern africa bodge
- SourceDataset_ESRISHAPE = \\map-fs1.ndph.ox.ac.uk\map_data\master_geometries\Admin_Units\Global\MAP\2019\MG_5K\admin2019_0_MG_5K.shp   # Source Esri Shapefile(s)

Readers:
- GEOTIFF_1: GEOTIFF from $(Environmental_Limits) in EPSG:4326
- ESRISHAPE_1: ESRISHAPE from $(SourceDataset_ESRISHAPE)

Writers:
- ESRISHAPE_2: ESRISHAPE to $(IntermediateFolder) in EPSG:4326
- GEOTIFF_2: GEOTIFF to $(OutputFolder) in EPSG:4326

Note: Save them!
test_2000 (writer GEOTIFF_2)

Bookmark: Read the polygons from the DB using the provided SQL
Creator
    GEOMTYPE = Geometry Object
    NUM = 1
    CREATED -> AttributeCreator_3
AttributeCreator_3
    ATTR_TABLE = SET_TO _sqlPath = $(FME_MF_DIR_USERTYPED)\$(SQL_Filename)
    -> AttributeFileReader
AttributeFileReader
    CHAR_ENCODING = utf-8
    DEST_ATTR = _sqlContent
    FILE_NAME = $(SQL_Filename)
    -> SQLExecutor [INITIATOR]
SQLExecutor
    COMBINE_ATTRS = Result Attributes Only
    COMBINE_GEOM = Initiator Geometry Only
    DATASET = datahub-prod
    EXPOSED_ATTRIBUTE_LIST = area_id,area_name,geom,year
    FORMAT = POSTGRES
    POSTGRES_NAMED_CONNECTION = datahub-prod--tunnel
    POSTGRES_QUERY_FEATURE_TYPES_FOR_MERGE_FILTERS = Yes
    POSTGRES_READ_TIME_WITH_TIMEZONE = Yes
    SQL_STATEMENT = @Value(_sqlContent)
    RESULT -> GeometryReplacer

Bookmark: Tell FME to use the DB geom
Note: We used an SQLExecutor, not a PostGIS reader, so FME doesn't automatically "get" their geometry.
GeometryReplacer
    KIND_LONG = OGC Well Known Binary
    REMOVE_ATTRIBUTE = Yes
    SOURCE = @Value(geom)
    -> GeometryValidator
    -> posthoc_limits_polygons_pf (writer ESRISHAPE_2)
GeometryValidator
    ANGULAR_TOLERANCE_CHOICE = Automatic
    ARC_ENDPOINT_TOLERANCE_MODE = Auto
    AREA_ORIENTATION = AREA_ORIENTATION
    CHECK_AREA_CHOICE = No
    CHECK_HOLE_TOUCHING_POLYGON = No
    CONNECT_Z_MODE_SI = First Wins
    CONNECT_Z_MODE_TR = First Wins
    CONSECUTIVE_IDENTICAL_VERTICES_2D = CONSECUTIVE_IDENTICAL_VERTICES_2D
    DUP_COORDS_CHECK_Z = Yes
    FLIP_APPEARANCES_CHOICE = Yes
    ISSUE_ATTR_NAME = _issues
    MISSING_TEXTURE_COORDINATES = MISSING_TEXTURE_COORDINATES
    MISSING_VERTEX_NORMALS = MISSING_VERTEX_NORMALS
    NAN_REMOVAL = NAN_REMOVAL
    NULL_REMOVAL = NULL_REMOVAL
    OGC_SIMPLE_CHECK = OGC_SIMPLE_CHECK
    OGC_VALID_CHECK = OGC_VALID_CHECK
    OGC_VERSION_CHOICE = 1.2.0
    ORIENTATION_CHECK_DIR = Valid
    PLANAR_SURFACE = PLANAR_SURFACE
    PRESETS = All
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SELF_INTERSECTING = SELF_INTERSECTING
    SHELL_VALIDATION = SHELL_VALIDATION
    SOLID_VOID_REPAIR = SOLID_VOID_REPAIR
    SUMMARY = Detailed
    THICKNESS_TOLERANCE_CHOICE = Automatic
    TYPE_REPAIR = TYPE_REPAIR
    PASSED -> Aggregator
    FAILED -> Duff_Geometry
    REPAIRED -> Aggregator
Duff_Geometry: Inspector
Note: Save them as a shapefile for reference only
posthoc_limits_polygons_pf (writer ESRISHAPE_2)
    attributes: area_id char(200), area_name char(200), year char(200)

Bookmark: Rasterize the polygons
Note: Just do as one multipart per year, more efficient
Aggregator
    ACCUM_ATTRS_NAME = Drop Incoming Attributes
    AGGREGATE_TYPE = Homogeneous Collection (If Possible)
    GROUP_BY = year
    MODE = Geometry - Assemble One Level
    ORDERED = No
    SEP = ,
    AGGREGATE -> AttributeCreator
AttributeCreator
    ATTR_TABLE = SET_TO _inlim = 0
    -> 3DForcer
Note: The feature to raster converter (NumericRasterizer) reads the Z coordinate of the features rather than an attribute, so, give them one
3DForcer
    KEEPZVAL = No
    ZVALATTR = @Value(_inlim)
    -> NumericRasterizer
Note: This is configured to match the 5k mastergrids. MUST BE CHANGED if we do 1k or anything else
NumericRasterizer
    ANTI_ALIASING = No
    BACKGROUND_VALUE = 1
    COLUMNS = 8640
    FILL_WITH_NODATA = No
    GROUND_EXTENTS_MAX_X = 180
    GROUND_EXTENTS_MAX_Y = -60
    GROUND_EXTENTS_MIN_X = -180
    GROUND_EXTENTS_MIN_Y = 85
    GROUP_BY = year
    INTERPRETATION_TYPE = Int32
    ROWCOL_OR_CELLSIZE = RowsColumns
    ROWS = 3480
    SPECIFY_GROUND_EXTENTS = Specify ground extents
    TOLERANCE = 0.5
    RASTER -> RasterBandNodataSetter_3
RasterBandNodataSetter_3
    NODATA_VALUE = -9999
    REPLACE_CELL_VALUES = No
    -> RasterExpressionEvaluator [B]

Bookmark: Multiply existing lims to give overall mask
Note: The zero-API polygons are "cut out", i.e. set to zero, against the existing static mask that is derived from environmental factors / travel health guidelines. Read this file, and multiply it by each new raster.
Note: As of 2018-09-14, the static file used here is one which has zero in all non-endemic countries, on top of the environmental factors . / This new file was prepared by Jen according to the NA model method in the GBD config file. / We could alternatively stick with the previous static limits file and do the non-endemic mask afterwards.
GEOTIFF (reader GEOTIFF_1)
    -> RasterInterpretationCoercer
RasterInterpretationCoercer
    COLOR_TO_NUMERIC = Bounded cast
    FLOAT_TO_INTEGER = Round
    INTERPRETATION = Int32
    NUMERIC_TO_NUMERIC = Bounded cast
    -> RasterBandNodataSetter_2
RasterBandNodataSetter_2
    NODATA_VALUE = -9999
    REPLACE_CELL_VALUES = Yes
    -> RasterExpressionEvaluator [A]
RasterExpressionEvaluator
    EXPRESSION_LIST = INTERPRETATION_LIST "INT32" EXPRESSION_LIST "A[0]*B[0]"
    MODE = Two Rasters
    RESULT -> CoordinateSystemSetter
CoordinateSystemSetter
    COORDSYS = LL-WGS84
    -> AttributeCreator_2

Bookmark: Prepare attributes for output
AttributeCreator_2
    ATTR_TABLE = SET_TO _outname = Pf_PostHoc_ZeroAPIForcing_Limits_@Value(year)_5k
    -> AttributeExposer
AttributeExposer
    ATTR_LIST = geotiff_number_of_bits_per_cell
    -> AttributeRemover
AttributeRemover
    REMOVE_ATTRS = geotiff_number_of_bits_per_cell
    -> FeatureReader [INITIATOR]
    -> Junction
Note: To the Bodging
Junction
    -> Junction_2

Bookmark: Apply Bodges: 1
Note: The new masks, ready for bodging
Junction_2
    -> RasterMosaicker
Note: Use the mask from 2014/15 Nature paper in ZAF, NAM, and BWA because it looks nicer
Note: Use a featurereader to read the 2015 Nature Africa mask (modified to just have 1=stable 0=all others) once for each new mask (just the way that the mosaicker works - need one copy for each)
FeatureReader
    ATTRIBUTES = GEOTIFF,
    ATTR_ACCUM_MODE = Merge Initiator and Result
    ATTR_CONFLICT_RES = Use Result
    COMBINE_GEOM = Use Result
    DATASET = $(OldLimitsFileForBodge)
    FORMAT = GEOTIFF
    GEOTIFF_APPLY_GCPS = NO
    GEOTIFF_FEATURE_TYPE_NAME = FORMAT_NAME
    GEOTIFF_IGNORE_RASTER_TYPE_KEY = No
    GEOTIFF_PREFER_FILE_CS_UNITS = Yes
    GEOTIFF_READER_META_ATTRIBUTES = fme_dataset fme_basename
    GEOTIFF_READ_OFFSETS_IN_CS_UNITS = No
    GEOTIFF_USE_SEARCH_ENVELOPE = NO
    INTERACT = <No Spatial Filter>
    OUTPUT_FEATURES_DISPLAY = Schema and Data Features
    GEOTIFF -> Clipper [CLIPPEE]
admin2019_0_MG_5K (reader ESRISHAPE_1)
    attributes: ISO char(3), Admn_Level long, Name_0 char(254), ID_0 long, Code_0 char(20), Type_0 char(100), Source char(254), area_id long
    -> Tester
Tester
    BOOL_OP = OR
    TEST_CLAUSE = TEST @Value(ISO) IN ZAF,NAM,BWA
    PASSED -> Clipper [CLIPPER]
Note: Clip the 2015 nature mask to the bodgee countries
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = Yes
    VAL_SOURCE = Clippee Only
    INSIDE -> FeatureHolder
Note: Ensure the bodgestamps arrive last to mosaicker by holding onto them
FeatureHolder
    -> RasterBandInterpretationCoercer_2
Note: Recode nodata and value type to match
RasterBandInterpretationCoercer_2
    COLOR_TO_NUMERIC = Bounded cast
    FLOAT_TO_INTEGER = Round
    INTERPRETATION = Int32
    NUMERIC_TO_NUMERIC = Bounded cast
    -> RasterBandNodataSetter
RasterBandNodataSetter
    NODATA_VALUE = -9999
    REPLACE_CELL_VALUES = Yes
    -> RasterMosaicker
Note: Bodge it!
RasterMosaicker
    ACCUM_ATTRS_NAME = Use Attributes From One Feature
    GROUP_BY = _outname
    INTERPOLATION_TYPE_NAME = Nearest Neighbor
    MERGE_PALETTES_NAME = Yes
    NODATA_OVERWRITE = No
    OVERLAPPING_VALUES = last
    SNAPPING_TYPE_NAME = Resample
    -> DontDoAnythingElseForNow

Bookmark: Apply Bodges: 2
Note: HAHA sucks to be you, future me or whoever else reads this
Note: Chances are we'll end up adding further bodges. Previous examples now removed include setting all of Peru to 1
DontDoAnythingElseForNow: AttributeRemover
    -> test_2000 (writer GEOTIFF_2)

Bookmark: Generate a zero-API mask for each year.
Note: The actual logic of which polygons to mask out (i.e. set to zero; prevent modelling) is complex based on API data and a hierarchy of where / when it is and isn't present. That logic is in the following file https://map-fs1.ndph.ox.ac.uk/gitlab/root/rds/blob/develop/installation/releases/Compute_and_Insert_API/15_Create_Zero_Masks.sql / Here we just read the table resulting from that, and rasterize the geometries it contains (one raster per year), using a pixel value of 0, to give the areas which must be set to zero in the post-hoc masks

Bookmark: Apply Bodges
Note: In this section we do a load of random unjustified shit that got tacked on to make things look nicer despite any lack of real justification. Prior to 2018-09-14 these were in separate workbenches, adding to the joyous confusion as various intermediary copies got or didn't get overwritten. Currently there's only one known bodge section, some of the others got rolled back into the SQL prequel step, but this bookmark can easily be expanded with a mere drag of the mouse when the inevitable happens. Likely bodges include setting areas to 1 (the earlier step only sets 0)
