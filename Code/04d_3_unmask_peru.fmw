FME workspace 04d_3_unmask_peru.fmw

Parameters:
- SourceDataset_GEOTIFF_2 = E:\Data\Harry\Documents\dial-a-map\fix_gbd_limits_with_old_africa_mask\out_only_fix_in_ZAF\Pf_PostHoc_ZeroAPIForcing_Limits_2*_5k.tif   # Source GeoTIFF File(s)
- DestDataset_GEOTIFF = E:\Data\Harry\Documents\dial-a-map\fix_gbd_limits_with_old_africa_mask\out_unmask_peru   # Destination GeoTIFF Folder
- SourceDataset_ESRISHAPE = \\map-fs1.ndph.ox.ac.uk\map_data\GBD2017\Processing\Spatial_Data\MAP_Admin_Units\GBD2017_MAP_MG_5K_All-Units_Master-Geometries\MG_5K_GBD2017_ADMIN0.shp   # Source Esri Shapefile(s)
- DestDataset_GEOTIFF_4 = E:\Data\Harry\Documents\dial-a-map\fix_gbd_limits_with_old_africa_mask\out_unmask_peru   # Destination GeoTIFF Folder

Readers:
- GEOTIFF_1: GEOTIFF from $(SourceDataset_GEOTIFF_2) in LL-WGS84
- ESRISHAPE_1: ESRISHAPE from $(SourceDataset_ESRISHAPE)

Writers:
- GEOTIFF_2: GEOTIFF to $(DestDataset_GEOTIFF)
- GEOTIFF_3: GEOTIFF to $(DestDataset_GEOTIFF_4)

MG_5K_GBD2017_ADMIN0 (reader ESRISHAPE_1) [off]
    attributes: area_id long, fdef_id long, area_fstp char(100), area_fggt char(10), area_dset char(100), area_name char(120), iso3 char(3)
    -> Tester
Tester [off]
    TEST_MODE = Automatic
    TEST_DESCRIPTION = ""
    TEST_CLAUSE = TEST @Value(iso3) = PER
    BOOL_OP = OR
    PASSED -> 3DForcer
3DForcer [off]
    ZVALATTR = 1
    KEEPZVAL = No
    -> NumericRasterizer
NumericRasterizer [off]
    SPECIFY_GROUND_EXTENTS = Specify ground extents
    TOLERANCE = 0.5
    GROUND_EXTENTS_MIN_Y = -60
    ROWS = 3480
    COLUMNS = 8640
    GROUND_EXTENTS_MIN_X = -180
    FILL_WITH_NODATA = Yes
    INTERPRETATION_TYPE = Int32
    GROUND_EXTENTS_MAX_X = 180
    ROWCOL_OR_CELLSIZE = RowsColumns
    GROUND_EXTENTS_MAX_Y = 85
    BACKGROUND_VALUE = -9999
    ANTI_ALIASING = No
    RASTER -> peru_unmask (writer GEOTIFF_2)
peru_unmask (writer GEOTIFF_2) [off]
Note: Read the previous iteration of the masks based on environmental limits and post-hoc masking polygons
GEOTIFF (reader GEOTIFF_1)
    -> AttributeRenamer
AttributeRenamer
    ATTR_TABLE = RENAME_SET_DEFAULT fme_basename > _outname
    -> RasterBandInterpretationCoercer
    -> FeatureReader [INITIATOR]
FeatureReader
    GEOTIFF_USE_SEARCH_ENVELOPE = NO
    GEOTIFF_APPLY_GCPS = No
    GEOTIFF_FEATURE_TYPE_NAME = FORMAT_NAME
    GEOTIFF_IGNORE_RASTER_TYPE_KEY = No
    ATTR_CONFLICT_RES = Use Result
    OUTPUT_FEATURES_DISPLAY = Schema and Data Features
    INTERACT = <No Spatial Filter>
    FORMAT = GEOTIFF
    ATTR_ACCUM_MODE = Merge Initiator and Result
    GEOTIFF_READER_META_ATTRIBUTES = fme_dataset fme_basename
    GEOTIFF_READ_OFFSETS_IN_CS_UNITS = No
    DATASET = E:\Data\Harry\Documents\dial-a-map\fix_gbd_limits_with_old_africa_mask\out_unmask_peru\peru_unmask.tif
    GEOTIFF_PREFER_FILE_CS_UNITS = Yes
    COMBINE_GEOM = Use Result
    <OTHER> -> FeatureHolder
Note: Ensure the old africa masks arrive last to mosaicker by holding onto them
FeatureHolder
    -> RasterBandInterpretationCoercer_2
Note: Recode nodata and value type to match
RasterBandInterpretationCoercer_2
    INTERPRETATION = Int32
    NUMERIC_TO_NUMERIC = Bounded cast
    COLOR_TO_NUMERIC = Bounded cast
    FLOAT_TO_INTEGER = Round
    -> RasterBandNodataSetter
RasterBandNodataSetter
    NODATA_VALUE = -9999
    REPLACE_CELL_VALUES = Yes
    -> RasterMosaicker
RasterBandInterpretationCoercer
    INTERPRETATION = Int32
    NUMERIC_TO_NUMERIC = Bounded cast
    COLOR_TO_NUMERIC = Bounded cast
    FLOAT_TO_INTEGER = Round
    -> RasterMosaicker
RasterMosaicker
    OVERLAPPING_VALUES = last
    GROUP_BY = _outname
    INTERPOLATION_TYPE_NAME = Nearest Neighbor
    SNAPPING_TYPE_NAME = Resample
    ACCUM_ATTRS_NAME = Use Attributes From One Feature
    MERGE_PALETTES_NAME = Yes
    NODATA_OVERWRITE = No
    -> GEOTIFF (writer GEOTIFF_3)
GEOTIFF (writer GEOTIFF_3)
