FME workspace 04d_1_prepare_posthoc_limits_initial_pv.fmw
Startup Python:
      # GBD - Archive outputs from any previous run
      # A version of this script should be run as a startup script in any GBD stages that are run using FME
      import fme
      import os, glob, datetime

      # build the paths based on the template stage folder layout relative to where the workbench itself is
      # Use abspath because fme occasionally does some weird escaping syntax on FME_MF_DIR
      codepath = os.path.abspath(fme.macroValues['FME_MF_DIR'])
      rootpath = os.path.dirname(codepath)
      # For this stage we have two types of run that should be considered separately so maintain subfolders below Checkpoint_Outputs
      checkpoint_path = os.path.join(rootpath, 'Checkpoint_Outputs', 'Pv')
      archive_path = os.path.join(checkpoint_path, 'Archive')

      prev_run_metadata_file = os.path.join(checkpoint_path, 'run_metadata.txt')
      if os.path.exists(prev_run_metadata_file):
          with open(prev_run_metadata_file, 'r') as f:
              prevRunTag = f.readline().strip("\n\r") + "-" + f.readline().strip("\n\r")
          # move them to a new subfolder under the archive named by runtime
          outdir = os.path.join(archive_path, prevRunTag)
          outdir_intermediate = os.path.join(outdir, "intermediates")
          outdir_out = os.path.join(outdir, "output")
          os.makedirs(outdir_intermediate)
          os.makedirs(outdir_out)
          # move everything except the readme file and the archive folder itself
          checkpoint_wildcard = os.path.join(checkpoint_path, '*')
          to_move = [f for f in glob.glob(checkpoint_wildcard)
              if not (os.path.basename(f).lower().startswith('readme'))
              and not (os.path.basename(f).lower() == 'archive')]
          for f in to_move:
              os.rename(f, os.path.join(outdir, os.path.basename(f)))

      else:
          # check if there are any outputs there- the folder might be clean so no problem
          if len(glob.glob(os.path.join(checkpoint_path,"*.tif"))) > 0:
              # cause an error
              logger = open(FME_LogFileName,'a')
              logger.write("Previous output data found but cannot find previous run metadata file. Please archive manually to continue!")
              raise Exception("Previous output data found but cannot find previous run metadata file. Please archive manually to continue!")
Shutdown Python:
      # FME python shutdown script to write out the metadata of this run, so that subsequent runs
      # will be able to read that metadata and use it to archive the outputs
      import fme
      import os, datetime
      # build the paths based on the template stage folder layout relative to where the workbench itself is
      codepath = os.path.abspath(fme.macroValues['FME_MF_DIR'])
      rootpath = os.path.dirname(codepath)
      checkpoint_path = os.path.join(rootpath, 'Checkpoint_Outputs', 'Pv')

      githash_file = os.path.join(codepath, 'githash.txt')
      if os.path.exists(githash_file):
          with open(githash_file, 'r') as f:
              githash = str(f.readline()) # str in case it's an all-numeric hash
      else:
          # cause an error
          assert False
      outTag = datetime.datetime.now().strftime('%Y_%m_%d_%H_%M_%S') + '\n' + githash
      outMDFile = os.path.join(checkpoint_path, 'run_metadata.txt')
      with open(outMDFile, 'w') as f:
          f.write(outTag)

Parameters:
- Environmental_Limits = \\map-fs1.ndph.ox.ac.uk\map_data\GBD2017\Processing\Spatial_Data\Static_Limits\Pv_Limits_EnvironmentalOnly_Endemic2017Only_5k.tif   # The existing environmental limits raster
- OutputFolder = ..\Checkpoint_Outputs\Pv   # Output folder - should be relative path to Checkpoint_Outputs
- IntermediateFolder = ..\Intermediary_Outputs   # Intermediate Output folder - should be relative path to Intermediary_Outputs
- SQL_Filename = zero_forcing_polygon_query_pv.sql   # SQL file in workbench folder containing the query

Readers:
- GEOTIFF_1: GEOTIFF from $(Environmental_Limits)

Writers:
- GEOTIFF_2: GEOTIFF to $(OutputFolder) in EPSG:4326
- ESRISHAPE_1: ESRISHAPE to $(IntermediateFolder) in EPSG:4326

GeometryReplacer
    KIND_LONG = OGC Well Known Binary
    REMOVE_ATTRIBUTE = Yes
    SOURCE = @Value(geom)
    -> GeometryValidator
    -> posthoc_limits_polygons_pv (writer ESRISHAPE_1)
Note: Save them as a shapefile for reference only
posthoc_limits_polygons_pv (writer ESRISHAPE_1)
    attributes: area_id char(200), area_name char(200), year char(200)
GeometryValidator
    ANGULAR_TOLERANCE_CHOICE = Automatic
    ARC_ENDPOINT_TOLERANCE_MODE = Auto
    AREA_ORIENTATION = AREA_ORIENTATION
    CHECK_AREA_CHOICE = No
    CHECK_HOLE_TOUCHING_POLYGON = No
    CONNECT_Z_MODE_SI = First Wins
    CONNECT_Z_MODE_TR = First Wins
    CONSECUTIVE_IDENTICAL_VERTICES_2D = CONSECUTIVE_IDENTICAL_VERTICES_2D
    DUP_COORDS_CHECK_Z = Yes
    FLIP_APPEARANCES_CHOICE = Yes
    ISSUE_ATTR_NAME = _issues
    MISSING_TEXTURE_COORDINATES = MISSING_TEXTURE_COORDINATES
    MISSING_VERTEX_NORMALS = MISSING_VERTEX_NORMALS
    NAN_REMOVAL = NAN_REMOVAL
    NULL_REMOVAL = NULL_REMOVAL
    OGC_SIMPLE_CHECK = OGC_SIMPLE_CHECK
    OGC_VALID_CHECK = OGC_VALID_CHECK
    OGC_VERSION_CHOICE = 1.2.0
    ORIENTATION_CHECK_DIR = Valid
    PLANAR_SURFACE = PLANAR_SURFACE
    PRESETS = All
    REPAIR = Yes
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    SELF_INTERSECTING = SELF_INTERSECTING
    SHELL_VALIDATION = SHELL_VALIDATION
    SOLID_VOID_REPAIR = SOLID_VOID_REPAIR
    SUMMARY = Detailed
    THICKNESS_TOLERANCE_CHOICE = Automatic
    TYPE_REPAIR = TYPE_REPAIR
    PASSED -> Aggregator
    FAILED -> Duff_Geometry
    REPAIRED -> Aggregator
Duff_Geometry: Inspector

Bookmark: Read the polygons from the DB using the provided SQL
Creator
    GEOMTYPE = Geometry Object
    NUM = 1
    CREATED -> AttributeCreator_3
AttributeCreator_3
    ATTR_TABLE = SET_TO _sqlPath = $(FME_MF_DIR_USERTYPED)\$(SQL_Filename)
    -> AttributeFileReader
AttributeFileReader
    CHAR_ENCODING = utf-8
    DEST_ATTR = _sqlContent
    FILE_NAME = $(SQL_Filename)
    -> SQLExecutor [INITIATOR]
SQLExecutor
    COMBINE_ATTRS = Result Attributes Only
    COMBINE_GEOM = Initiator Geometry Only
    DATASET = datahub-prod
    EXPOSED_ATTRIBUTE_LIST = area_id,area_name,geom,year
    FORMAT = POSTGRES
    POSTGRES_NAMED_CONNECTION = datahub-prod--tunnel
    POSTGRES_QUERY_FEATURE_TYPES_FOR_MERGE_FILTERS = Yes
    POSTGRES_READ_TIME_WITH_TIMEZONE = Yes
    SQL_STATEMENT = @Value(_sqlContent)
    RESULT -> GeometryReplacer

Bookmark: Rasterize the polygons
Note: Just do as one multipart per year, more efficient
Aggregator
    ACCUM_ATTRS_NAME = Drop Incoming Attributes
    AGGREGATE_TYPE = Homogeneous Collection (If Possible)
    GROUP_BY = year
    MODE = Geometry - Assemble One Level
    ORDERED = No
    SEP = ,
    AGGREGATE -> AttributeCreator
AttributeCreator
    ATTR_TABLE = SET_TO _inlim = 0
    -> 3DForcer
Note: The feature to raster converter (NumericRasterizer) reads the Z coordinate of the features rather than an attribute, so, give them one
3DForcer
    KEEPZVAL = No
    ZVALATTR = @Value(_inlim)
    -> NumericRasterizer
Note: This is configured to match the 5k mastergrids. MUST BE CHANGED if we do 1k or anything else
NumericRasterizer
    ANTI_ALIASING = No
    BACKGROUND_VALUE = 1
    COLUMNS = 8640
    FILL_WITH_NODATA = No
    GROUND_EXTENTS_MAX_X = 180
    GROUND_EXTENTS_MAX_Y = -60
    GROUND_EXTENTS_MIN_X = -180
    GROUND_EXTENTS_MIN_Y = 85
    GROUP_BY = year
    INTERPRETATION_TYPE = Int32
    ROWCOL_OR_CELLSIZE = RowsColumns
    ROWS = 3480
    SPECIFY_GROUND_EXTENTS = Specify ground extents
    TOLERANCE = 0.5
    RASTER -> RasterBandNodataSetter_3
RasterBandNodataSetter_3
    NODATA_VALUE = -9999
    REPLACE_CELL_VALUES = No
    -> RasterExpressionEvaluator [B]

Bookmark: Multiply existing lims to give overall mask
Note: Read the "normal" i.e. environmental / travel-health limits
GEOTIFF (reader GEOTIFF_1)
    -> RasterInterpretationCoercer
RasterInterpretationCoercer
    COLOR_TO_NUMERIC = Bounded cast
    FLOAT_TO_INTEGER = Round
    INTERPRETATION = Int32
    NUMERIC_TO_NUMERIC = Bounded cast
    -> RasterBandNodataSetter_2
RasterBandNodataSetter_2
    NODATA_VALUE = -9999
    REPLACE_CELL_VALUES = Yes
    -> RasterExpressionEvaluator [A]
RasterExpressionEvaluator
    EXPRESSION_LIST = INTERPRETATION_LIST "INT32" EXPRESSION_LIST "A[0]*B[0]"
    MODE = Two Rasters
    RESULT -> AttributeCreator_2

Bookmark: Write outputs 1 per year
AttributeCreator_2
    ATTR_TABLE = SET_TO _outname = Pv_PostHoc_ZeroAPIForcing_Limits_@Value(year)_5k
    -> AttributeExposer
AttributeExposer
    ATTR_LIST = geotiff_number_of_bits_per_cell
    -> AttributeRemover
AttributeRemover
    REMOVE_ATTRS = geotiff_number_of_bits_per_cell
    -> test_2000 (writer GEOTIFF_2)
test_2000 (writer GEOTIFF_2)
