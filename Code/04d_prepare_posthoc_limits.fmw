FME workspace 04d_prepare_posthoc_limits.fmw

Parameters:
- SourceDataset_GEOTIFF = \\map-fs1.ndph.ox.ac.uk\map_data\GBD2016\Limits\Pf_Limits_2016_NoAPI_5k.tif   # Source GeoTIFF File(s)
- DestDataset_GEOTIFF = $(FME_MF_DIR)v05   # Destination GeoTIFF Folder
- DestDataset_ESRISHAPE = $(FME_MF_DIR)v05   # Destination Esri Shapefile Folder

Readers:
- GEOTIFF_1: GEOTIFF from $(SourceDataset_GEOTIFF)

Writers:
- GEOTIFF_2: GEOTIFF to $(DestDataset_GEOTIFF)
- ESRISHAPE_1: ESRISHAPE to $(DestDataset_ESRISHAPE)

SQLCreator_2 [off]
    DATASET = rds-dev
    EXPOSED_ATTRIBUTE_LIST = area_dset_code,area_name,geom,shape_file_id,year
    SQL_STATEMENT:
      select shape_file_id, year, area_dset_code, ST_AsEWKB(area_multi_polygon) geom, area_name
      from
      staging.gbd2016_zero_afi_mask m
      JOIN rds.area_insts a
      ON m.shape_file_id = a.area_id
      --where year = 1999
      order by  year, shape_file_id
    FORMAT = POSTGRES
    POSTGRES_QUERY_FEATURE_TYPES_FOR_MERGE_FILTERS = Yes
    POSTGRES_NAMED_CONNECTION = rds-dev
Note: Original map-prod4 version preserved for posterity
SQLCreator [off]
    DATASET = map-prod4 - joes special db
    EXPOSED_ATTRIBUTE_LIST = area_dset_code,area_name,geom,shape_file_id,year
    SQL_STATEMENT:
      SELECT
        shape_file_id,
        year,
        area_dset_code,
        ST_AsEWKB(area_multi_polygon) geom,
        area_name
      FROM (
             SELECT
               shape_file_id,
               year
             FROM staging.gbd2016_zero_afi_mask
             UNION
             SELECT
               polys.shape_file_id,
               years.year
             FROM (SELECT 91341123 AS shape_file_id
                   UNION SELECT 91341129
                   UNION SELECT 91341130
                   UNION SELECT 91341131) polys
               CROSS JOIN (SELECT DISTINCT year
                           FROM staging.gbd2016_zero_afi_mask) years
           ) m
        JOIN rds.area_insts a
          ON m.shape_file_id = a.area_id
      ORDER BY shape_file_id, year;
    FORMAT = POSTGRES
    POSTGRES_QUERY_FEATURE_TYPES_FOR_MERGE_FILTERS = Yes
    POSTGRES_NAMED_CONNECTION = map-prod4 - joes special db
Note: Get the zero API polygons from the DB using SQL from Joe
SQLCreator_3
    DATASET = RDS on MAP-FS1 (RDS instance)
    EXPOSED_ATTRIBUTE_LIST = area_dset_code,area_name,geom,shape_file_id,year
    SQL_STATEMENT:
      SELECT
        shape_file_id,
        year,
        area_dset_code,
        ST_AsEWKB(area_multi_polygon) geom,
        area_name
      FROM (
             SELECT
               shape_file_id,
               year
             FROM staging.gbd2016_zero_afi_mask
             UNION
             SELECT
               polys.shape_file_id,
               years.year
             FROM (SELECT 91341123 AS shape_file_id
                   UNION SELECT 91341129
                   UNION SELECT 91341130
                   UNION SELECT 91341131) polys
               CROSS JOIN (SELECT DISTINCT year
                           FROM staging.gbd2016_zero_afi_mask) years
           ) m
        JOIN rds.area_insts a
          ON m.shape_file_id = a.area_id
      ORDER BY shape_file_id, year;
    FORMAT = POSTGRES
    POSTGRES_QUERY_FEATURE_TYPES_FOR_MERGE_FILTERS = Yes
    POSTGRES_NAMED_CONNECTION = RDS on MAP-FS1 (RDS instance)
    RESULT -> GeometryReplacer
GeometryReplacer
    REMOVE_ATTRIBUTE = Yes
    KIND_LONG = OGC Well Known Binary
    SOURCE = @Value(geom)
    -> GeometryValidator
    -> posthoc_limits_polygons (writer ESRISHAPE_1)
    -> Shapes_Orig
Shapes_Orig: Inspector
Note: Save them as a shapefile for reference only
posthoc_limits_polygons (writer ESRISHAPE_1)
    attributes: area_dset_ char(200), area_name char(200), shape_file char(200), year char(200)
GeometryValidator
    CHECK_HOLE_TOUCHING_POLYGON = No
    SHELL_VALIDATION = SHELL_VALIDATION
    PLANAR_SURFACE = PLANAR_SURFACE
    REPAIR = Yes
    ISSUE_ATTR_NAME = _issues
    OGC_VERSION_CHOICE = 1.2.0
    NAN_REMOVAL = NAN_REMOVAL
    TYPE_REPAIR = TYPE_REPAIR
    CONSECUTIVE_IDENTICAL_VERTICES_2D = CONSECUTIVE_IDENTICAL_VERTICES_2D
    THICKNESS_TOLERANCE_CHOICE = Automatic
    CONNECT_Z_MODE_SI = First Wins
    OGC_SIMPLE_CHECK = OGC_SIMPLE_CHECK
    SUMMARY = Detailed
    MISSING_TEXTURE_COORDINATES = MISSING_TEXTURE_COORDINATES
    NULL_REMOVAL = NULL_REMOVAL
    OGC_VALID_CHECK = OGC_VALID_CHECK
    MISSING_VERTEX_NORMALS = MISSING_VERTEX_NORMALS
    CONNECT_Z_MODE_TR = First Wins
    SOLID_VOID_REPAIR = SOLID_VOID_REPAIR
    ARC_ENDPOINT_TOLERANCE_MODE = Auto
    FLIP_APPEARANCES_CHOICE = Yes
    AREA_ORIENTATION = AREA_ORIENTATION
    ANGULAR_TOLERANCE_CHOICE = Automatic
    CHECK_AREA_CHOICE = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    ORIENTATION_CHECK_DIR = Valid
    DUP_COORDS_CHECK_Z = Yes
    SELF_INTERSECTING = SELF_INTERSECTING
    PRESETS = All
    PASSED -> Aggregator
    FAILED -> GeometryValidator_Failed
    REPAIRED -> Aggregator
GeometryValidator_Failed: Inspector
Aggregator
    GROUP_BY = year
    SEP = ,
    AGGREGATE_TYPE = Homogeneous Collection (If Possible)
    MODE = Geometry - Assemble One Level
    ACCUM_ATTRS_NAME = Drop Incoming Attributes
    ORDERED = No
    AGGREGATE -> AttributeCreator
AttributeCreator
    ATTR_TABLE = SET_TO _inlim = 0
    -> 3DForcer
Note: The feature to raster converter (NumericRasterizer) reads the Z coordinate of the features rather than an attribute
3DForcer
    KEEPZVAL = No
    ZVALATTR = @Value(_inlim)
    -> NumericRasterizer
    -> Shapes
Shapes: Inspector
NumericRasterizer
    GROUP_BY = year
    GROUND_EXTENTS_MIN_Y = 85
    FILL_WITH_NODATA = No
    GROUND_EXTENTS_MIN_X = -180
    BACKGROUND_VALUE = 1
    ROWCOL_OR_CELLSIZE = RowsColumns
    INTERPRETATION_TYPE = Int32
    SPECIFY_GROUND_EXTENTS = Specify ground extents
    ROWS = 3480
    COLUMNS = 8640
    TOLERANCE = 0.5
    ANTI_ALIASING = No
    GROUND_EXTENTS_MAX_X = 180
    GROUND_EXTENTS_MAX_Y = -60
    RASTER -> RasterBandNodataSetter_3
RasterBandNodataSetter_3
    NODATA_VALUE = -9999
    REPLACE_CELL_VALUES = No
    -> RasterExpressionEvaluator [B]
    -> RasterBandNodataSetter_3_Output
RasterBandNodataSetter_3_Output: Inspector [off]
Note: Read the "normal" i.e. environmental / travel-health limits
GEOTIFF (reader GEOTIFF_1)
    -> RasterInterpretationCoercer
RasterInterpretationCoercer
    COLOR_TO_NUMERIC = Bounded cast
    NUMERIC_TO_NUMERIC = Bounded cast
    INTERPRETATION = Int32
    FLOAT_TO_INTEGER = Round
    -> RasterBandNodataSetter_2
RasterBandNodataSetter_2
    NODATA_VALUE = -9999
    REPLACE_CELL_VALUES = Yes
    -> RasterExpressionEvaluator [A]
RasterExpressionEvaluator
    MODE = Two Rasters
    EXPRESSION_LIST = INTERPRETATION_LIST "INT32" EXPRESSION_LIST "A[0]*B[0]"
    RESULT -> AttributeCreator_2
AttributeCreator_2
    ATTR_TABLE = SET_TO _outname = Pf_PostHoc_ZeroAPIForcing_Limits_@Value(year)_5k
    -> AttributeExposer
AttributeExposer
    ATTR_LIST = geotiff_number_of_bits_per_cell
    -> AttributeRemover
AttributeRemover
    REMOVE_ATTRS = geotiff_number_of_bits_per_cell
    -> test_2000 (writer GEOTIFF_2)
test_2000 (writer GEOTIFF_2)
